module transitions {
  namespace "http://sssup.it/transitions";
  prefix ev;

  import ietf-yang-push {
    prefix yp;
  }

  organization
    "Scuola Superiore Sant'Anna Network and Services Laboratory";

  contact
    " Editor: Matteo Dallaglio
              <mailto:m.dallaglio@sssup.it>
    ";

  description
    "This module contains a YANG definitions of events and generic reactions.";

  revision 2016-03-15 {
    description "Initial Revision.";
    reference 
      "RFC xxxx: A YANG data model for the description of events and reactions";
  }
  
  // identity statements

  identity TRANSITION {
      description "Base for all types of event";
  }

  identity ON_CHANGE {
      base TRANSITION;
      description 
        "The event when the database changes.";
  }

  // typedef statements

  typedef transition-type {
    type identityref {
      base TRANSITION;
    }
  }

  typedef transition-id-type {
    type uint32;
  }


  // grouping statements
  grouping action-block {
    leaf id {
      type transition-id-type;
    }
    leaf type {
      type enumeration {
        enum CONDITIONAL_OP;
        enum SIMPLE_OP;
      }
      mandatory true;
    }

    grouping execution-top {
      anyxml execute {
        description "Represent the action to perform";
      }
      leaf next-action {
        type transition-id-type;
        description "the id of the next action to execute";
      }
    }

    container conditional {
      when "../type = 'CONDITIONAL_OP'";
      leaf statement {
        type string;
        mandatory true;
        description 
          "The statement to be evaluated before execution.
          E.g. if a=b";
      }
      container true {
        uses execution-top;
      }
      container false {
        uses execution-top;
      }
    }

    container simple {
      when "../type = 'SIMPLE_OP'";
      description 
        "Simple execution of an action without checking any condition";
      uses execution-top;
    }
  }

  grouping action-top {
    list action {
      key "id";
      ordered-by user;
      uses action-block;
    }
  }

  grouping on-change {
    description 
      "Event occuring when a modification of one or more
       objects occurs";

    leaf threshold-parameter {
      type decimal64;
    }

    leaf threshold-operator {
      type string;
    }


  }

  grouping transition-top {
    leaf name {
      type string;
      mandatory true;
    }

    

    leaf description {
      type string;
    }

    // list of all possible events
    uses on-change {
      when "type = 'ON_CHANGE'";
    }

    container transition-action {
      uses action-top;
    }
  }

  grouping transitions-top {
    container transitions {
      list transition {
        key "name";
        uses transition-top;
      }
    }
  }


  // data definition statements

  uses transitions-top;

  // extension statements

  // feature statements

  // augment statements

  // rpc statements

  // notification statements


}//module transitions
